# -*- coding: utf-8 -*-

# Macro Begin: C:\PyApp\FREECAD-stuff\Macro\BO.FCMacro +++++++++++++++++++++++++++++++++++++++++++++++++
import FreeCAD

# Macro End: C:\PyApp\FREECAD-stuff\Macro\BO.FCMacro +++++++++++++++++++++++++++++++++++++++++++++++++
