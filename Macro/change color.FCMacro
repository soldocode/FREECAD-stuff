# Macro Begin: C:\SOLDINISNC\FREECAD\Macro\change color.FCMacro +++++++++++++++++++++++++++++++++++++++++++++++++
import FreeCAD

# Macro End: C:\SOLDINISNC\FREECAD\Macro\change color.FCMacro +++++++++++++++++++++++++++++++++++++++++++++++++
