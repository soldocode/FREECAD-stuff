import FreeCAD as FC

def changeColor(object,scope,new_color):
	actual_color=object.ViewObject.DiffuseColor[0]
	num_faces=len(object.Shape.Faces)
	col_array=[actual_color]*num_faces

	for c in scope:
		col_array[c]=new_color

	object.ViewObject.DiffuseColor=col_array	

SCOPE=[7,16,6,1,13]
COLOR=(0.8,0.2,0.2)

sel=Gui.Selection.getSelectionEx()[0]
changeColor(sel.Object, SCOPE,COLOR)
