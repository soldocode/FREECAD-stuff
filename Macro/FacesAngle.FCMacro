import math
from FreeCAD import Vector

sels=Gui.Selection.getSelectionEx()

if len(sels)==1:
    s1=sels[0].SubObjects[0]
    s2=sels[0].SubObjects[1]
elif len(sels)==2:
    s1=sels[0].SubObjects[0]
    s2=sels[1].SubObjects[0]

vns1 = s1.normalAt(0,0)
vns2 = s2.normalAt(0,0)
ref=Vector( 0,0,1)

a1=ref.getAngle( vns1)
a2=ref.getAngle( vns2)
print ('diff=',a1-a2)

alpha = math.degrees( a1-a2)

print ('angle between faces:',alpha)
