# -*- coding: utf-8 -*-

# Macro Begin: C:\SOLDINISNC\FREECAD\Macro\cubo.FCMacro +++++++++++++++++++++++++++++++++++++++++++++++++
import FreeCAD
import Sketcher
import PartDesign
import Import
import PySide


App.newDocument("Senza nome")
#App.setActiveDocument("Senza_nome1")
#App.ActiveDocument=App.getDocument("Senza_nome1")
#Gui.ActiveDocument=Gui.getDocument("Senza_nome1")
#Gui.activateWorkbench("DraftWorkbench")
#Gui.activateWorkbench("PartWorkbench")
#Gui.activateWorkbench("PartDesignWorkbench")
App.activeDocument().addObject('Sketcher::SketchObject','Sketch')
App.activeDocument().Sketch.Placement = App.Placement(App.Vector(0.000000,0.000000,0.000000),App.Rotation(0.000000,0.000000,0.000000,1.000000))
#Gui.activeDocument().activeView().setCamera('#Inventor V2.1 ascii \n OrthographicCamera {\n viewportMapping ADJUST_CAMERA \n position 0 0 87 \n orientation 0 0 1  0 \n nearDistance -112.88701 \n farDistance 287.28702 \n aspectRatio 1 \n focalDistance 87 \n height 143.52005 }')
#Gui.activeDocument().setEdit('Sketch')
geoList = []
geoList.append(Part.Line(App.Vector(-31.195675,-23.122675,0),App.Vector(31.793684,-23.122675,0)))
geoList.append(Part.Line(App.Vector(31.793684,-23.122675,0),App.Vector(31.793684,25.514673,0)))
geoList.append(Part.Line(App.Vector(31.793684,25.514673,0),App.Vector(-31.195675,25.514673,0)))
geoList.append(Part.Line(App.Vector(-31.195675,25.514673,0),App.Vector(-31.195675,-23.122675,0)))
App.ActiveDocument.Sketch.addGeometry(geoList,False)
conList = []
conList.append(Sketcher.Constraint('Coincident',0,2,1,1))
conList.append(Sketcher.Constraint('Coincident',1,2,2,1))
conList.append(Sketcher.Constraint('Coincident',2,2,3,1))
conList.append(Sketcher.Constraint('Coincident',3,2,0,1))
conList.append(Sketcher.Constraint('Horizontal',0))
conList.append(Sketcher.Constraint('Horizontal',2))
conList.append(Sketcher.Constraint('Vertical',1))
conList.append(Sketcher.Constraint('Vertical',3))
App.ActiveDocument.Sketch.addConstraint(conList)

App.ActiveDocument.Sketch.addGeometry(Part.Circle(App.Vector(-19.435001,14.950008,0),App.Vector(0,0,1),2.552710),False)
App.ActiveDocument.Sketch.addGeometry(Part.Circle(App.Vector(15.448339,13.754009,0),App.Vector(0,0,1),5.277633),False)
App.ActiveDocument.Sketch.addGeometry(Part.Circle(App.Vector(-15.249003,-15.149340,0),App.Vector(0,0,1),2.711227),False)
#Gui.getDocument('Senza_nome1').resetEdit()
App.getDocument('Senza_nome1').recompute()
App.activeDocument().addObject("PartDesign::Pad","Pad")
App.activeDocument().Pad.Sketch = App.activeDocument().Sketch
App.activeDocument().Pad.Length = 10.0
App.ActiveDocument.recompute()
#Gui.activeDocument().hide("Sketch")
#Gui.activeDocument().setEdit('Pad',0)
App.ActiveDocument.Pad.Length = 12.000000
App.ActiveDocument.Pad.Reversed = 0
App.ActiveDocument.Pad.Midplane = 0
App.ActiveDocument.Pad.Length2 = 100.000000
App.ActiveDocument.Pad.Type = 0
App.ActiveDocument.Pad.UpToFace = None
App.ActiveDocument.recompute()
#Gui.activeDocument().resetEdit()
__objs__=[]
__objs__.append(FreeCAD.getDocument("Senza_nome1").getObject("Pad"))


fname= PySide.QtGui.QFileDialog.getSaveFileName()                   
print(fname)

Import.export(__objs__,fname[0])

del __objs__
# Macro End: C:\SOLDINISNC\FREECAD\Macro\cubo.FCMacro +++++++++++++++++++++++++++++++++++++++++++++++++
